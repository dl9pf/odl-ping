module ping-provider-impl {

    yang-version 1;
    namespace "urn:opendaylight:params:xml:ns:yang:controller:config:ping-provider:impl";
    prefix "ping-provider-impl";

    import config { prefix config; revision-date 2013-04-05; }
    import opendaylight-md-sal-binding { prefix mdsal; revision-date 2013-10-28; }

    description
        "This module contains the base YANG definitions for
        ping-provider impl implementation.";

    revision "2014-05-23" {
        description
            "Initial revision.";
    }

    // This is the definition of the service implementation as a module identity.
    identity ping-provider-impl {
            base config:module-type;

            // Specifies the prefix for generated java classes.
            config:java-name-prefix PingProvider;
    }

    // Augments the 'configuration' choice node under modules/module.  
    // We consume the three main services, RPCs, DataStore, and Notifications 
    augment "/config:modules/config:module/config:configuration" {
        case ping-provider-impl {
            when "/config:modules/config:module/config:type = 'ping-provider-impl'";
    
            container rpc-registry {
                uses config:service-ref {
                    refine type {
                        mandatory true;
                        config:required-identity mdsal:binding-rpc-registry;
                    }
                }
            }
        }
    }
}
